-- **************************************************************
--
-- Apollo PDU Descriptions.
--
-- **************************************************************
APOLLO-PDU-Descriptions


DEFINITIONS AUTOMATIC TAGS ::=

BEGIN

APOLLO-PDU	    ::= SEQUENCE {
    version		Version,
    transactionId	INTEGER (0..65535),
    procedure		Procedure,
    ...
}

Procedure	    ::= CHOICE {
    error		Error,
    response		Response,
    createTable		CreateTable,
    deleteTable		DeleteTable,
    openTable		OpenTable,
    closeTable		CloseTable,
    tableInfo		TableInfo,
    read		Read,
    write		Write,
    update		Update,
    delete		Delete,
    readRange		ReadRange,
    readRangeN		ReadRangeN,
    batchWrite		BatchWrite,
    first		First,
    last		Last,
    seek		Seek,
    next		Next,
    prev		Prev,
    ...
}

-- **************************************************************
--
-- Apollo Procedure Definitions.
--
-- **************************************************************
BatchWrite	    ::= SEQUENCE {
    tableName		FieldName,
    deleteKeys		SEQUENCE OF Key,
    writeKvps		SEQUENCE OF KeyColumnsPair,
    ...
}

CloseTable	    ::= SEQUENCE {
    tableName		FieldName,
    ...
}

CreateTable	    ::= SEQUENCE {
    tableName		FieldName,
    keys		SEQUENCE OF FieldName,
    tableOptions	SET OF TableOption,
    ...

}

Delete		    ::= SEQUENCE {
    tableName		FieldName,
    key			Key,
    ...

}

DeleteTable	    ::= SEQUENCE {
    tableName		FieldName,
    ...

}

Error		    ::= SEQUENCE {
    cause		Cause OPTIONAL,
    ...

}

OpenTable	    ::= SEQUENCE {
    tableName		FieldName,
    ...

}

Read		   ::=	SEQUENCE {
    tableName		FieldName,
    key			Key,
    ...

}

ReadRange	    ::= SEQUENCE {
    tableName		FieldName,
    keyRange		KeyRange,
    limit		INTEGER,
    ...

}

ReadRangeN	    ::= SEQUENCE {
    tableName		FieldName,
    startKey		Key,
    n			INTEGER,
    ...

}

Response	    ::= SEQUENCE {
    result		Result OPTIONAL,
    moreDataToBeSent	BOOLEAN OPTIONAL,
    ...

}

Result		    ::= CHOICE {
    columns		Columns,
    keyColumnsPair	KeyColumnsPair,
    keyColumnsList	KeyColumnsList,
    propList		SET OF Field,
    kcpIt		KcpIt,
    ...

}

TableInfo	    ::= SEQUENCE {
    tableName           FieldName,
    attributes		SET OF FieldName OPTIONAL,
    ...

}

Write		    ::= SEQUENCE {
    tableName		FieldName,
    key			Key,
    columns		Columns,
    ...

}

Update		    ::= SEQUENCE {
    tableName		FieldName,
    key			Key,
    updateOperations	SEQUENCE OF UpdateOperation,
    ...

}

First		    ::= SEQUENCE {
    tableName		FieldName,
    ...

}

Last		    ::= SEQUENCE {
    tableName		FieldName,
    ...

}

Seek		    ::= SEQUENCE {
    tableName		FieldName,
    key			Key,
    ...

}

Next		    ::= SEQUENCE {
    it			It,
    ...

}

Prev		    ::= SEQUENCE {
    it			It,
    ...

}

-- **************************************************************
--
-- Common IE Definitions.
--
-- **************************************************************

Columns		    ::= SEQUENCE (SIZE (1..maxNumOfColumns)) OF Field

Cause		    ::= CHOICE {
    transport		IA5String (SIZE(1..maxCauseLength)),
    protocol		IA5String (SIZE(1..maxCauseLength)),
    system		IA5String (SIZE(1..maxCauseLength)),
    misc		IA5String (SIZE(1..maxCauseLength)),
    ...

}

Comparator	    ::= ENUMERATED {
    descending		(0),
    ascending		(1),
    ...
}

Continuation	    ::= SEQUENCE {
    complete		BOOLEAN,
    key			Key OPTIONAL,
    ...
}

DataModel	    ::= ENUMERATED {
    kv			(0),
    array		(1),
    map			(2),
    ...

}

Field		    ::= SEQUENCE {
    name		FieldName,
    value		Value,
    ...

}

-- Limit Fieldname Chars to (a..z)
FieldName	    ::= IA5String (SIZE(1..64))

Key		    ::= SEQUENCE (SIZE (1..maxNumOfKeyFields)) OF Field

KeyRange	    ::= SEQUENCE {
    start		Key,
    end			Key,
    ...

}

KeyColumnsPair	    ::= SEQUENCE {
    key			Key,
    columns		Columns,
    ...

}

KeyColumnsList	    ::= SEQUENCE {
    list		SET OF KeyColumnsPair,
    continuation	Continuation OPTIONAL,
    ...
}

KcpIt		    ::= SEQUENCE {
    keyColumnsPair	KeyColumnsPair,
    it			It,
    ...

}

It		    ::= OCTET STRING (SIZE(1..512))

SizeMargin	    ::= CHOICE {
    megabytes		INTEGER,
    ...
}

TableOption	    ::= CHOICE {
    type		Type,
    dataModel		DataModel,
    wrapper		Wrapper,
    memWrapper		Wrapper,
    comparator		Comparator,
    timeSeries		BOOLEAN,
    shards		INTEGER (1..8192),
    distributed		BOOLEAN,
    replicationFactor	INTEGER,
    hashExclude		SEQUENCE OF FieldName,
    ...
}

TimeMargin	    ::= CHOICE {
    seconds		INTEGER,
    minutes		INTEGER,
    hours		INTEGER,
    ...
}

Type		    ::= ENUMERATED {
    leveldb		(0),
    etsLeveldb		(1),
    leveldbWrapped	(2),
    etsLeveldbWrapped	(3),
    ...

}

InstructionType	    ::= ENUMERATED {
    increment		(0),
    overwrite		(1),
    ...
}

UpdateInstruction   ::= SEQUENCE {
    instruction		InstructionType,
    threshold		INTEGER OPTIONAL,
    setValue		INTEGER OPTIONAL,
    ...
}

UpdateOperation	    ::= SEQUENCE {
    field		FieldName,
    updateInstruction	UpdateInstruction,
    value		Value,
    defaultValue	Value OPTIONAL,
    ...
}

Value		    ::= CHOICE {
    bool		BOOLEAN,
    int			INTEGER,
    binary		OCTET STRING,
    null		NULL,
    double		OCTET STRING (SIZE(8)),
    string		UTF8String,
    ...
}

Version		    ::= SEQUENCE {
    major		INTEGER (0..15),
    minor		INTEGER (0..15),
    ...

}

Wrapper		    ::= SEQUENCE {
    numOfBuckets	INTEGER (1..100000),
    timeMargin		TimeMargin OPTIONAL,
    sizeMargin		SizeMargin OPTIONAL,
    ...

}

maxNumOfKeyFields   INTEGER ::= 100

maxNumOfColumns	    INTEGER ::= 10000

maxNumOfIndexes	    INTEGER ::= 8

maxCauseLength	    INTEGER ::= 64

END
